InterledgerProtocol
DEFINITIONS
AUTOMATIC TAGS ::=
BEGIN

IMPORTS
    UInt64
    FROM GenericTypes

    Address,
    Timestamp
    FROM InterledgerTypes
;

ForwardedPaymentData ::= SEQUENCE {
    -- Destination ILP Address
    account Address,
    -- Information for recipient (transport layer information)
    data OCTET STRING (SIZE (0..32767)),
    -- Enable ASN.1 Extensibility
    extensions SEQUENCE {
        ...
    }
}

InterledgerProtocolPaymentData ::= SEQUENCE {
    -- Amount which must be received at the destination
    amount UInt64,
    -- Destination ILP Address
    account Address,
    -- Information for recipient (transport layer information)
    data OCTET STRING (SIZE (0..32767)),
    -- Enable ASN.1 Extensibility
    extensions SEQUENCE {
        ...
    }
}

InterledgerProtocolErrorData ::= SEQUENCE {
    -- Standardized error code
    code IA5String (SIZE (3)),
    -- Corresponding error name
    name IA5String,
    -- Participant that originally emitted the error
    triggeredBy Address,
    -- Participants that forwarded the error
    forwardedBy SEQUENCE OF Address,
    -- Time of emission
    triggeredAt Timestamp,
    -- Additional data
    data OCTET STRING (SIZE (0..8192)),
    -- Enable ASN.1 Extensibility
    extensions SEQUENCE {
        ...
    }
}

InterledgerProtocolFulfillmentData ::= SEQUENCE {
    -- Information for sender (transport layer information)
    data OCTET STRING (SIZE (0..32767))
}

END
